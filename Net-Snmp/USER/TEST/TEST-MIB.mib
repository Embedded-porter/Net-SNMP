--
-- TEST-MIB.my
-- MIB generated by MG-SOFT Visual MIB Builder Version 6.0  Build 88
-- Tuesday, April 14, 2020 at 16:21:12
--
	TEST-MIB DEFINITIONS ::= BEGIN
 
		IMPORTS
			OBJECT-GROUP			
				FROM SNMPv2-CONF			
			enterprises, Integer32, OBJECT-TYPE, MODULE-IDENTITY			
				FROM SNMPv2-SMI;
	
	
		-- 1.3.6.1.4.1.1
		a MODULE-IDENTITY 
			LAST-UPDATED "202004141615Z"		-- April 14, 2020 at 16:15 GMT
			ORGANIZATION 
				"Organization."
			CONTACT-INFO 
				"Contact-info."
			DESCRIPTION 
				"Description."
			::= { enterprises 1 }
	
--
-- Node definitions
--
	
		-- 1.3.6.1.4.1.1.1
		b OBJECT IDENTIFIER ::= { a 1 }

		
		-- 1.3.6.1.4.1.1.1.1
		test OBJECT-TYPE
			SYNTAX Integer32
			MAX-ACCESS read-write
			STATUS current
			DESCRIPTION
				"Description."
			::= { b 1 }

		
		-- 1.3.6.1.4.1.1.2
		group OBJECT-GROUP
			OBJECTS { test }
			STATUS current
			DESCRIPTION 
				"Description."
			::= { a 2 }
	
	END

--
-- TEST-MIB.my
--
